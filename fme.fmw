FME workspace fme.fmw

Parameters:
- SourceDataset_GEOTIFF = ""$(FME_MF_DIR)PUNKT1\ras250_gb\data\HP.tif" "$(FME_MF_DIR)PUNKT1\ras250_gb\data\HT.tif" "$(FME_MF_DIR)PUNKT1\ras250_gb\data\HU.tif" "$(FME_MF_DIR)PUNKT1\ras250_gb\data\HW.tif" "$(FME_MF_DIR)PUNKT1\ras250_gb\data\HX.tif" "$(FME_MF_DIR)PUNKT1\ras250_gb\data\HY.tif" "$(FME_MF_DIR)PUNKT1\ras250_gb\data\HZ.tif" "$(FME_MF_DIR)PUNKT1\ras250_gb\data\NA.tif" "$(FME_MF_DIR)PUNKT1\ras250_gb\data\NB.tif" "$(FME_MF_DIR)PUNKT1\ras250_gb\data\NC.tif" "$(FME_MF_DIR)PUNKT1\ras250_gb\data\ND.tif" "$(FME_MF_DIR)PUNKT1\ras250_gb\data\NF.tif" "$(FME_MF_DIR)PUNKT1\ras250_gb\data\NG.tif" "$(FME_MF_DIR)PUNKT1\ras250_gb\data\NH.tif" "$(FME_MF_DIR)PUNKT1\ras250_gb\data\NJ.tif" "$(FME_MF_DIR)PUNKT1\ras250_gb\data\NK.tif" "$(FME_MF_DIR)PUNKT1\ras250_gb\data\NL.tif" "$(FME_MF_DIR)PUNKT1\ras250_gb\data\NM.tif" "$(FME_MF_DIR)PUNKT1\ras250_gb\data\NN.tif" "$(FME_MF_DIR)PUNKT1\ras250_gb\data\NO.tif" "$(FME_MF_DIR)PUNKT1\ras250_gb\data\NR.tif" "$(FME_MF_DIR)PUNKT1\ras250_gb\data\NS.tif" "$(FME_MF_DIR)PUNKT1\ras250_gb\data\NT.tif" "$(FME_MF_DIR)PUNKT1\ras250_gb\data\NU.tif" "$(FME_MF_DIR)PUNKT1\ras250_gb\data\NW.tif" "$(FME_MF_DIR)PUNKT1\ras250_gb\data\NX.tif" "$(FME_MF_DIR)PUNKT1\ras250_gb\data\NY.tif" "$(FME_MF_DIR)PUNKT1\ras250_gb\data\NZ.tif" "$(FME_MF_DIR)PUNKT1\ras250_gb\data\OV.tif" "$(FME_MF_DIR)PUNKT1\ras250_gb\data\SC.tif" "$(FME_MF_DIR)PUNKT1\ras250_gb\data\SD.tif" "$(FME_MF_DIR)PUNKT1\ras250_gb\data\SE.tif" "$(FME_MF_DIR)PUNKT1\ras250_gb\data\SH.tif" "$(FME_MF_DIR)PUNKT1\ras250_gb\data\SJ.tif" "$(FME_MF_DIR)PUNKT1\ras250_gb\data\SK.tif" "$(FME_MF_DIR)PUNKT1\ras250_gb\data\SM.tif" "$(FME_MF_DIR)PUNKT1\ras250_gb\data\SN.tif" "$(FME_MF_DIR)PUNKT1\ras250_gb\data\SO.tif" "$(FME_MF_DIR)PUNKT1\ras250_gb\data\SP.tif" "$(FME_MF_DIR)PUNKT1\ras250_gb\data\SR.tif" "$(FME_MF_DIR)PUNKT1\ras250_gb\data\SS.tif" "$(FME_MF_DIR)PUNKT1\ras250_gb\data\ST.tif" "$(FME_MF_DIR)PUNKT1\ras250_gb\data\SU.tif" "$(FME_MF_DIR)PUNKT1\ras250_gb\data\SV.tif" "$(FME_MF_DIR)PUNKT1\ras250_gb\data\SW.tif" "$(FME_MF_DIR)PUNKT1\ras250_gb\data\SX.tif" "$(FME_MF_DIR)PUNKT1\ras250_gb\data\SY.tif" "$(FME_MF_DIR)PUNKT1\ras250_gb\data\SZ.tif" "$(FME_MF_DIR)PUNKT1\ras250_gb\data\TA.tif" "$(FME_MF_DIR)PUNKT1\ras250_gb\data\TF.tif" "$(FME_MF_DIR)PUNKT1\ras250_gb\data\TG.tif" "$(FME_MF_DIR)PUNKT1\ras250_gb\data\TL.tif" "$(FME_MF_DIR)PUNKT1\ras250_gb\data\TM.tif" "$(FME_MF_DIR)PUNKT1\ras250_gb\data\TQ.tif" "$(FME_MF_DIR)PUNKT1\ras250_gb\data\TR.tif" "$(FME_MF_DIR)PUNKT1\ras250_gb\data\TV.tif""   # Source GeoTIFF File(s) or URL(s)
- FEATURE_TYPES =
- SourceDataset_SHAPEFILE = $(FME_MF_DIR)PUNKT2\Data\GB\scotland_and_wales_const_region.shp   # Source Esri Shapefile(s)
- FEATURE_TYPES_2 =
- DestDataset_GEOTIFF = $(FME_MF_DIR)DANE\Results.gdb   # Destination GeoTIFF Folder
- SourceDataset_GEOTIFF_2 = ""$(FME_MF_DIR)DANE\Results.gdb\extents.tif" "$(FME_MF_DIR)DANE\Results.gdb\extents_1.tif" "$(FME_MF_DIR)DANE\Results.gdb\extents_2.tif" "$(FME_MF_DIR)DANE\Results.gdb\extents_3.tif" "$(FME_MF_DIR)DANE\Results.gdb\extents_4.tif" "$(FME_MF_DIR)DANE\Results.gdb\extents_5.tif" "$(FME_MF_DIR)DANE\Results.gdb\extents_6.tif" "$(FME_MF_DIR)DANE\Results.gdb\extents_7.tif" "$(FME_MF_DIR)DANE\Results.gdb\extents_8.tif" "$(FME_MF_DIR)DANE\Results.gdb\extents_9.tif" "$(FME_MF_DIR)DANE\Results.gdb\extents_10.tif" "$(FME_MF_DIR)DANE\Results.gdb\extents_11.tif" "$(FME_MF_DIR)DANE\Results.gdb\extents_12.tif" "$(FME_MF_DIR)DANE\Results.gdb\extents_13.tif" "$(FME_MF_DIR)DANE\Results.gdb\extents_14.tif" "$(FME_MF_DIR)DANE\Results.gdb\extents_15.tif" "$(FME_MF_DIR)DANE\Results.gdb\extents_16.tif" "$(FME_MF_DIR)DANE\Results.gdb\extents_17.tif" "$(FME_MF_DIR)DANE\Results.gdb\extents_18.tif" "$(FME_MF_DIR)DANE\Results.gdb\extents_19.tif" "$(FME_MF_DIR)DANE\Results.gdb\extents_20.tif" "$(FME_MF_DIR)DANE\Results.gdb\extents_21.tif" "$(FME_MF_DIR)DANE\Results.gdb\extents_22.tif" "$(FME_MF_DIR)DANE\Results.gdb\extents_23.tif" "$(FME_MF_DIR)DANE\Results.gdb\extents_24.tif" "$(FME_MF_DIR)DANE\Results.gdb\extents_25.tif" "$(FME_MF_DIR)DANE\Results.gdb\extents_26.tif" "$(FME_MF_DIR)DANE\Results.gdb\extents_27.tif" "$(FME_MF_DIR)DANE\Results.gdb\extents_28.tif" "$(FME_MF_DIR)DANE\Results.gdb\extents_29.tif" "$(FME_MF_DIR)DANE\Results.gdb\extents_30.tif" "$(FME_MF_DIR)DANE\Results.gdb\extents_31.tif" "$(FME_MF_DIR)DANE\Results.gdb\extents_32.tif" "$(FME_MF_DIR)DANE\Results.gdb\extents_33.tif" "$(FME_MF_DIR)DANE\Results.gdb\extents_34.tif" "$(FME_MF_DIR)DANE\Results.gdb\extents_35.tif" "$(FME_MF_DIR)DANE\Results.gdb\extents_36.tif" "$(FME_MF_DIR)DANE\Results.gdb\extents_37.tif" "$(FME_MF_DIR)DANE\Results.gdb\extents_38.tif" "$(FME_MF_DIR)DANE\Results.gdb\extents_39.tif" "$(FME_MF_DIR)DANE\Results.gdb\extents_40.tif" "$(FME_MF_DIR)DANE\Results.gdb\extents_41.tif" "$(FME_MF_DIR)DANE\Results.gdb\extents_42.tif" "$(FME_MF_DIR)DANE\Results.gdb\extents_43.tif" "$(FME_MF_DIR)DANE\Results.gdb\extents_44.tif" "$(FME_MF_DIR)DANE\Results.gdb\extents_45.tif" "$(FME_MF_DIR)DANE\Results.gdb\extents_46.tif" "$(FME_MF_DIR)DANE\Results.gdb\extents_47.tif" "$(FME_MF_DIR)DANE\Results.gdb\extents_48.tif" "$(FME_MF_DIR)DANE\Results.gdb\extents_49.tif" "$(FME_MF_DIR)DANE\Results.gdb\extents_50.tif" "$(FME_MF_DIR)DANE\Results.gdb\extents_51.tif" "$(FME_MF_DIR)DANE\Results.gdb\extents_52.tif" "$(FME_MF_DIR)DANE\Results.gdb\extents_53.tif" "$(FME_MF_DIR)DANE\Results.gdb\extents_54.tif" "$(FME_MF_DIR)DANE\Results.gdb\extents_55.tif""   # Source GeoTIFF File(s) or URL(s)
- FEATURE_TYPES_3 =
- DestDataset_POSTGIS_RASTER = FME   # Connection

Readers:
- GEOTIFF_1: GEOTIFF from $(SourceDataset_GEOTIFF)
- SHAPEFILE_1: SHAPEFILE from $(SourceDataset_SHAPEFILE)
- GEOTIFF_3: GEOTIFF from $(SourceDataset_GEOTIFF_2)

Writers:
- GEOTIFF_2: GEOTIFF to $(DestDataset_GEOTIFF)
- POSTGIS_RASTER_1: POSTGIS_RASTER to $(DestDataset_POSTGIS_RASTER)

GEOTIFF (reader GEOTIFF_1)
    -> Reprojector
Reprojector
    DEST = LL-WGS84
    INTERPOLATION_TYPE = NearestNeighbor
    RASTER_CELL_SIZE = PreserveCells
    RASTER_TOLERANCE = 0.0
    REPROJECTED -> RasterPropertyExtractor
RasterPropertyExtractor
    -> AttributeCreator
AttributeCreator
    ATTR_TABLE = SET_TO NewName (varchar(200)) = @Concatenate(fme_file_name,'_',fme_file_size)
    INPUT_PORT_CONNECTED = CONNECTED
    -> extents (writer GEOTIFF_2)
extents (writer GEOTIFF_2)
    attributes: NewName char(200), _num_bands largeint, _num_rows largeint, _num_columns largeint, _spacing_x float, _spacing_y float, _origin_x float, _origin_y float, _rotation_x float, _rotation_y float, _min_x float, _min_y float, _max_x float, _max_y float, _cell_origin_x float, _cell_origin_y float, _upper_left_x float, _upper_left_y float, _upper_right_x float, _upper_right_y float, _lower_right_x float, _lower_right_y float, _lower_left_x float, _lower_left_y float
scotland_and_wales_const_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE:
      TEST @Value(FILE_NAME) = SOUTH_WALES_CENTRAL_PER
      TEST @Value(FILE_NAME) = SOUTH_WALES_EAST_PER
      TEST @Value(FILE_NAME) = SOUTH_WALES_WEST_PER
    TEST_MODE = TEST
    PASSED -> Reprojector_2
Reprojector_2
    DEST = LL-WGS84
    INTERPOLATION_TYPE = NearestNeighbor
    RASTER_CELL_SIZE = PreserveCells
    RASTER_TOLERANCE = 0.0
    REPROJECTED -> Clipper [CANDIDATE]
GEOTIFF (reader GEOTIFF_3)
    -> Clipper [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_INTERIM
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> exports (writer POSTGIS_RASTER_1)
exports (writer POSTGIS_RASTER_1)
    attributes: name varchar(100), area_code varchar(3), descriptio varchar(50), file_name varchar(100), number int8, number0 int8, polygon_id int8, unit_id int8, code varchar(9), hectares float4, area float4, type_code varchar(2), descript0 varchar(25), type_cod0 varchar(3), descript1 varchar(36), _clipped char(3)
